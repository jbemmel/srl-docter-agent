module docter-agent {

    yang-version "1";

    // namespace
    namespace "urn:srl_test/docter-agent";

    prefix "docter_agent";

    import srl_nokia-common {
      prefix srl_nokia-comm;
    }

    // Note that this module needs to be in the path for source-directories
    import srl_nokia-extensions {
      prefix srl_nokia-ext;
    }

    revision "2021-04-11" {
        description "Initial revision";
        reference "TBD";
    }

    // This gets complicated with 'digits' and 'precision'
    typedef sla_type {
         type decimal64 {
             fraction-digits 3;
             // range "0 .. 99.999 | 100.0";
         }
    }

    grouping docter-agent-top {
        description "Top level grouping for docter agent sample app";

        container docter-agent {
            presence "presence container";
            srl_nokia-ext:stream-mode on_change;

            description "Top level enclosing container for auto config agent sample app
                         config and operational state data";

            // Placeholder for demo
            container health {
              srl_nokia-ext:delivery-node-override true;
              config false;

              //leaf last-updated {
              //  type srl_nokia-comm:date-and-time-delta;
              //}

              container route {
                presence "Route health container";
                leaf status {
                  type string;
                  default "green";
                }
                leaf availability {
                  type string;
                  default "100.000";
                }
                leaf count {
                  type uint32;
                }
                leaf-list values {
                  type string;
                  ordered-by user; // otherwise system will sort the values
                }
              }
            } // end health

            // Generalized health metrics
            container metrics { // workaround for disappearing data? Nope
               presence "Metrics container";
               srl_nokia-ext:delivery-node-override true;
               srl_nokia-ext:stream-mode on_change;
               config false;

               list metric {
                key name;
                leaf name { type string; }
                leaf status {
                  type string; // e.g. color
                  default "unknown";
                }
                leaf cause {
                  description "Latest contributing cause of degradation";
                  type string;
                }
                leaf status-summary {
                  description "Consolidated status string";
                  type string;
                }
                leaf status-detail {
                  description "Consolidated status string with details like port";
                  type string;
                }
                list contribution {
                  key name;
                  leaf name { type string; }
                  leaf status { type string; } // e.g. color
                  leaf availability { type string; } // optional
                  leaf-list reports { type string; } // detailed reports
                }
               }
            }

            // gNMI reporting to collectors
            container reports {
              srl_nokia-ext:delivery-node-override true;
              srl_nokia-ext:stream-mode on_change;
              config false;

              leaf last-updated {
                type srl_nokia-comm:date-and-time-delta;
              }

              leaf count {
                description "Number of events reported";
                type srl_nokia-comm:zero-based-counter64;
                default 0;
              }

              leaf filtered {
                description "Number of events suppressed by filter expression";
                type srl_nokia-comm:zero-based-counter64;
                default 0;
              }

              list events {
                key event;
                leaf event  { type string; }
                leaf name {
                  type string; // technically a leafref to obervations/name
                }
                leaf timestamp { type string; }
                leaf sample-period { type uint16; }
                leaf trigger { type string; }
                leaf-list values {
                  type string;
                  ordered-by user; // otherwise system will sort the values
                }
              }

              list availability {
                 key name;

                 leaf name {
                   type leafref {
                     path "../../../intensive-care/observe/name";
                    // // require-instance "true";
                   }
                   // type string;
                 }

                 leaf availability {
                   description "For sampled state variables, percentage of time that the value was present";
                   // type sla_type;
                   type string; // decimal, e.g. 99.999
                 }
                 leaf status {
                   description "Color set based on defined threshold(s)";
                   type string;
                 }
              }

              list history {
                 description "History of trigger condition values";
                 key name;

                 leaf name {
                   type leafref {
                    path "../../../intensive-care/observe/name";
                    // require-instance "true";
                   }
                 }

                 // subitem under subscription path
                 list path {
                  key path;
                  leaf path { type string; }

                  list event {
                    key t;
                    leaf t { type uint64; }
                    leaf v { type string; }
                    leaf filter {
                      description "Flag used to indicate an entry that did not match the filter";
                      type boolean;
                    }
                  }
                 }
              }
            }

            container intensive-care {
              leaf startup-delay {
                description "Optional time to wait (seconds) before starting gNMI subscription loop";
                type uint16;
                default 0;
              }
              list observe {
                key name;
                leaf name { type string; mandatory "true"; }
                list conditions {
                  key gnmi-path;
                  ordered-by user; // because values can be referenced by index
                  description "Set of conditions that must all be true for reporting";
                  min-elements 1;

                  leaf gnmi-path {
                    description "Path to local state variable to observe";
                    type string;
                    mandatory "true";
                  }
                  leaf update-path-match {
                    description "Regular expression to match updates, default empty (exact path match)";
                    type string;
                    default "";
                  }
                  leaf index {
                    description "Regular expression to apply to paths, for aggregating reports";
                    type string;
                  }
                  leaf filter {
                    description "Optional filter expression, for example != 'established'";
                    type string;
                  }
                  leaf reset {
                    description "Optional reset timer (seconds) to clear non-green state";
                    type uint16;
                  }
                  leaf value {
                    description "Optional Python expression to calculate a value to report";
                    type string;
                  }
                  leaf green {
                    description "Expression to report as 'green'";
                    type string;
                  }
                  leaf yellow {
                    description "Expression to report as 'yellow'";
                    type string;
                  }
                  leaf orange {
                    description "Expression to report as 'orange'";
                    type string;
                  }
                  leaf red {
                    description "Expression to report as 'red'";
                    type string;
                  }
                  leaf missing {
                    description "Expression to report when miss timer fires";
                    type string;
                    default "grey";
                  }
                  //leaf count {
                  //  description "Optional regex to count unique matches in reported paths, e.g. BGP neighbor IPs: '\\[neighbor=.*\\]'";
                  //  type string;
                  //}
                  leaf-list thresholds {
                    description "Boundary condition(s), single value for match=green or for example [80,95] for >80%=yellow, >95%=red";
                    ordered-by user; // otherwise system will sort the values
                    type string;
                  }
                  leaf sample-period {
                    description "Monitoring interval in seconds, default 0=on change";
                    type uint16;
                    default 0;
                  }
                  leaf history-window {
                    description "Time limit on history items to keep, in seconds";
                    type uint16;
                  }
                  leaf history-items {
                    description "Limit on the number of history items to keep in history";
                    type uint16;
                  }
                  leaf aggregate {
                    description "Optional aggregate function to apply to values";
                    type enumeration {
                      enum average;
                      enum sum;
                      enum minimum;
                      enum maximum;
                      enum no;
                    }
                    default "no";
                  }

                  leaf metric {
                    description "Health metric this item contributes to (optional)";
                    type string; // cannot refer to non-config leaf
                    // type leafref {
                    //  path "/docter-agent/health/metric/name";
                    // }

                    //must "count(../thresholds) > 0" {
                    //  error-message "Metric requires definition of threshold(s)";
                    //}
                  }
                }
                leaf-list report {
                  description "gNMI path of value to report when conditions are met";
                  type string;    // TODO pattern [label:] gnmi_path
                  min-elements 0; // Implicit report for condition path
                }
              } // end list observe
            } // end intensive-care

        }
    }

    // data definition statements
    uses docter-agent-top;
}
