module auto_config_agent {

    yang-version "1";

    // namespace
    namespace "urn:srl_test/auto-config-agent";

    prefix "auto_config_agent";

    // import srl_nokia-common {
    //    prefix srl_nokia-comm;
    // }

    // Note that this module needs to be in the path for source-directories
    import srl_nokia-extensions {
      prefix srl_nokia-ext;
    }

    revision "2021-04-11" {
        description "Initial revision";
        reference "TBD";
    }

    grouping auto-config-agent-top {
        description "Top level grouping for auto config agent sample app";

        container auto-config-agent {
            presence "presence container";
            description "Top level enclosing container for auto config agent sample app
                         config and operational state data";

            leaf role {
                description "Role of this node in the fabric (layer in the network)";
                type enumeration {
                 enum leaf;
                 enum spine;
                 // TODO enum superspine;
                }
            }
            leaf base-as {
                description "Baseline 2-byte or 4-byte Autonomous System to auto-assign";
                // type srl_nokia-comm:as-number;
                type uint32;
                default 65000; // Spines get this, each leaf gets base+rank
            }
            leaf peerlinks-prefix {
                description "IPv4 prefix range to use for auto-assigned peering links /31";
                // type srl_nokia-comm:ipv4-prefix;
                type string;
                default "192.168.0.0/24"; // enough for 128 /31 links
            }
            leaf loopbacks-prefix {
                description "IPv4 prefix range to use for auto-assigned loopback IPs /32";
                // type srl_nokia-comm:ipv4-prefix;
                type string;
                default "1.1.0.0/23"; // spines get 1.1.0.x, leaves 1.1.1.x
            }
            leaf max-spines {
                description "Maximum number of spines, controls IP link addressing; must match across fabric";
                type uint8;
                default 4; // Higher values require a larger peerlinks-prefix space
            }
            leaf max-leaves {
                description "Maximum number of leafs, controls AS allocation; must match across fabric";
                type uint16;
                default 16; // Currently only affects max AS that spines accept BGP peering from
            }

            container monitor {
             leaf flaps-monitoring-period {
                description "Monitoring period in minutes, default 1 hour";
                type uint16;
                default 60;
             }

             leaf flaps-per-period-threshold {
                description "Number of BFD flaps per period still considered acceptable";
                type uint32;
                default 0;
             }
             leaf max-flaps-history {
                description "Maximum number of flaps to retain, 0 = infinite";
                type uint32;
                default 0;
             }

            }

            // Info from state
            leaf total-bfd-flaps-last-period {
                type uint64;
                config false;
            }
            leaf total-route-flaps-last-period {
                type uint64;
                config false;
            }
            list peer {
                key peer-ip;
                config false;

                leaf peer-ip {
                  type string;
                }
                container bfd {
                 srl_nokia-ext:delivery-node-override true;
                 srl_nokia-ext:stream-mode sample=5;
                 presence "State BFD operational parameters";

                 leaf status {
                  type string;
                  default "red";
                 }
                 leaf flaps-last-period {
                  type uint32;
                 }
                 leaf flaps-history {
                  type string;
                 }
                 leaf last-flap-timestamp {
                   type string;
                 }
                }
                container routes {
                 srl_nokia-ext:delivery-node-override true;
                 srl_nokia-ext:stream-mode sample=5;
                 presence "State Routes operational parameters";

                 leaf status {
                  type string;
                 }
                 leaf flaps-last-period {
                  type uint64;
                 }
                 leaf flaps-history {
                  type string;
                 }
                 leaf last-flap-timestamp {
                   type string;
                 }
              }
            }
        }
    }

    // data definition statements
    uses auto-config-agent-top;
}
